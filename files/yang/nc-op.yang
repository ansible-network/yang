module nc-op {
  namespace "https://github.com/ansible-network/yang/nc-op";
  prefix "nc-op";
  import ietf-yang-metadata {
    prefix "md";
  }
  md:annotation operation {
        type string;
        description
            "annotations for netconf edit-config operation.";
      }
      description "NETCONF 'operation' attribute values";
}
